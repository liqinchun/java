module uplink {
    yang-version 1.1;
    namespace "https://inhandnetworks.com/yang/inhand-uplink";
    prefix "in-uplink";
    revision 2020-11-05;
    container uplink-services {
       list uplink-svc {
       key device-id;
               leaf device-id {
                 type string;
               }
               container wired {
                   list wan {
                     key name;
                     leaf name {
                       type string;
                     }
                     leaf ip-origin {
                       type string;
                     }
                     leaf gateway {
                       type string;
                     }
                     leaf ip-address {
                       type string;
                     }

                     leaf dns1 {
                          type string;
                     }
                     leaf dns2 {
                            type string;
                     }
                     leaf username {
                       type string;
                     }
                     leaf password {
                       type string;
                     }
                     leaf client-id {
                          type string;
                       }
                     leaf lease {
                          type uint32;
                          }
                   }
               }
               container wifi {
                 leaf ssid {
                   type string;
                 }

                leaf auth {
                  type string;
                }
                leaf encryption_algorithm {
                  type string;
                }

                leaf password {
                  type string;
                }
                leaf type {
                  type string;
                }
                leaf gateway {
                  type string;
                }
                leaf ip-address {
                  type string;
                }
                list dns {
                  key name;
                  leaf name {
                    type string;
                  }

                }

               }
       }
    }
}
